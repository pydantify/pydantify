module interfaces {
  namespace
  "http://ultraconfig.com.au/ns/yang/ultraconfig-interfaces";

  prefix if;

  description 'Example using just leafs, containers and modules';

  container interfaces {
    description 'Just a simple example of a container.';

    leaf name {
        type string;
        mandatory "true";
        description
            "Interface name. Example value: GigabitEthernet 0/0/0";
    }
    leaf complex-address {
        type string {
            pattern "(\d{1,3}\.){3}\d{1,3}";
        }
        mandatory "true";
        description
            "Interface IP address. Example value: 10.10.10.1";
    }
    leaf complex-port {
        type uint16 {
            range "1..99 | 1024..max";
        }
        mandatory "true";
        description
            "Port number. Example value: 8080";
    }
    leaf simple-port {
        type uint16 {
            range "1..max";
        }
        mandatory "true";
        description
            "Port number. Example value: 8080";
    }
  }
}
