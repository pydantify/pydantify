module interfaces {
  namespace
  "http://ultraconfig.com.au/ns/yang/ultraconfig-interfaces";

  prefix if;

  description 'A simple module to validate comments,'
    + ' typedefs, and pattern validators.'
    + ' Source: https://ultraconfig.com.au/blog/learn-yang-full-tutorial-for-beginners/';

  typedef dotted-quad {
    // Simple typedef with string pattern validator
    type string {
      pattern
        '(([0-9]|[1-9][0-9]|1[0-9][0-9]|2[0-4][0-9]|25[0-5])\.){3}'
          + '([0-9]|[1-9][0-9]|1[0-9][0-9]|2[0-4][0-9]|25[0-5])';
    }
    description
      "Four octets written as decimal numbers and
      separated with the '.' (full stop) character.";
  }

  container interfaces {
    list interface {
      key "name";
      description "Regular IPv4 address with subnet";
      leaf name {
        type string;
        mandatory "true";
        description
          "Interface name. Example value: GigabitEthernet 0/0/0";
      }
      leaf address {
        type dotted-quad;
        mandatory "true";
        description
          "Interface IP address. Example value: 10.10.10.1";
      }
      leaf subnet-mask {
        type dotted-quad;
        mandatory "true";
        description
          "Interface subnet mask. Example value: 255.255.255.0";
      }
      leaf enabled {
        type boolean;
        default "false";
        description
          "Enable or disable the interface. Example value: true";
      }
    }
  }
}
