module interfaces {
  namespace
  "http://ultraconfig.com.au/ns/yang/ultraconfig-interfaces";

  prefix if;

  description 'Example demonstrating "uses" keyword';

  grouping target {
    leaf address {
      type string;
      description "Target IP address";
    }
    leaf port {
      type string;
      description "Target port number";
    }
  }

  container peer {
    container destination {
      uses target;
    }
  }
}
