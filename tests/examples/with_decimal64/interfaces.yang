module interfaces {
  namespace
  "http://ultraconfig.com.au/ns/yang/ultraconfig-interfaces";

  prefix if;

  description 'Example using just leafs, containers and modules';

  container interfaces {
    description 'Just a simple example of a container.';

    leaf name {
        type string;
        mandatory "true";
        description
            "Interface name. Example value: GigabitEthernet 0/0/0";
    }

    leaf counter1 {
        type decimal64 {
          range "-20..3";
          fraction-digits 1;
        }
        config "false";
        description
            "Pkt Counter 1";
    }
  }
}
