module interfaces {
  namespace
  "http://ultraconfig.com.au/ns/yang/ultraconfig-interfaces";

  prefix if;

  description 'Example using just leafs, containers and modules';

  container interfaces {
    description 'Just a simple example of a container.';

    leaf name {
        type string;
        mandatory "true";
        description
            "Interface name. Example value: GigabitEthernet 0/0/0";
    }
    leaf address {
        type string;
        mandatory "true";
        description
            "Interface IP address. Example value: 10.10.10.1";
    }
    leaf port {
        type uint16;
        mandatory "true";
        description
            "Port number. Example value: 8080";
    }
  }
}
